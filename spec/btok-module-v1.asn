Btok-module-v1 {iso(1) member-body(2) by(112) 0 2 0 34 101 79 module(1) ver1(1)}
DEFINITIONS IMPLICIT TAGS ::=
BEGIN
  IMPORTS
    PublicKey
      FROM Bign-module-v2 {iso(1) member-body(2) by(112) 0 2 0 34 101 45 
        module(1) ver2(2)};

  btok OBJECT IDENTIFIER ::= {iso(1) member-body(2) by(112) 0 2 0 34 101 79}

  btok-bauth OBJECT IDENTIFIER ::= {btok 11}
  btok-bauth1 OBJECT IDENTIFIER ::= {btok 12}

  btok-attrs OBJECT IDENTIFIER ::= {btok 5}
  id-DocumentValidity OBJECT IDENTIFIER ::= {btok-attrs 1}
  id-AgeVerification OBJECT IDENTIFIER ::= {btok-attrs 2}
  id-PlaceVerification OBJECT IDENTIFIER ::= {btok-attrs 3}

  btok-access OBJECT IDENTIFIER ::= {btok 6}
  id-eIdAccess OBJECT IDENTIFIER ::= {btok-access 1}
  id-eSignAccess OBJECT IDENTIFIER ::= {btok-access 2}

  btok-apps OBJECT IDENTIFIER ::= {btok 7}
  id-eID OBJECT IDENTIFIER ::= {btok-apps 1}
  id-eSign OBJECT IDENTIFIER ::= {btok-apps 2}

  btok-cvext OBJECT IDENTIFIER ::= {btok 8}
  id-SignAuthExt OBJECT IDENTIFIER ::= {btok-cvext 1}

  SerialNumber ::= [APPLICATION 1] PrintableString(SIZE(14..18))
  IssuingState ::= [APPLICATION 2] Country
  DateOfExpiry ::= [APPLICATION 3] Date
  GivenName ::= [APPLICATION 4] UTF8String
  FamilyName ::= [APPLICATION 5] UTF8String
  MiddleName ::= [APPLICATION 6] UTF8String
  PersonalNumber ::= [APPLICATION 7] PrintableString(SIZE(7..64))
  DateOfBirth ::= [APPLICATION 8] Date
  PlaceOfBirth ::= [APPLICATION 9] GeneralPlace
  Nationality ::= [APPLICATION 10] Country
  Sex ::= [APPLICATION 11] ICAOSex
  OptionalDataR ::= [APPLICATION 12] SET OF OptionalData
  WrittenSignature ::= [APPLICATION 14] OCTET STRING
  DateOfIssuance ::= [APPLICATION 15] Date
  IssuanceBoard ::= [APPLICATION 16] UTF8String
  PlaceOfResidence ::= [APPLICATION 17] GeneralPlace
  DistrictID ::= [APPLICATION 18] PrintableString(SIZE(0..64))
  PhoneNumber ::= [APPLICATION 21] PrintableString
  EmailAddress ::= [APPLICATION 22] IA5String
  
  ICAOString ::= PrintableString(FROM("A".."Z" | " "))
  Country ::= ICAOString(SIZE(3))
  ICAOSex ::= PrintableString(FROM("M"|"F"|" "))
  Date ::= NumericString(SIZE(8))
  
  Place ::= SEQUENCE {
    street  [10] UTF8String OPTIONAL,
    city    [11] UTF8String,
    state   [12] UTF8String OPTIONAL,
    country [13] Country,
    zipcode [14] PrintableString OPTIONAL
  }
  
  GeneralPlace ::= CHOICE {
    structuredPlace Place,
    freetextPlace   [1] UTF8String,
    noPlaceInfo     [2] UTF8String
  }
  
  OptionalData ::= SEQUENCE {
    type  OBJECT IDENTIFIER,
    data  ANY DEFINED BY type OPTIONAL
  }

  AuthAuxData ::= [APPLICATION 7] SEQUENCE OF DiscretionaryDataTemplate

  DiscretionaryDataTemplate ::= [APPLICATION 19] SEQUENCE {
    objIdentifier  OBJECT IDENTIFIER,
    dataObjects    ANY DEFINED BY objIdentifier
  }

  CertHAT ::= [APPLICATION 76] SEQUENCE {
    objId              OBJECT IDENTIFIER,
    discretionaryData  OCTET STRING
  }

  CVCertificate ::= [APPLICATION 33] SEQUENCE {
    certificateBody                   [APPLICATION 78] SEQUENCE {
      certProfileIdentifier           [APPLICATION 41] INTEGER {v1(0)},
      certAuthorityReference          [APPLICATION 2]  CharString,
      publicKey                       [APPLICATION 73] PubKey,
      certHolderReference             [APPLICATION 32] CharString,
      certHolderAuthorizationTemplate [APPLICATION 76] CertHAT OPTIONAL,
      certEffectiveDate               [APPLICATION 37] CVDate,
      certExpirationDate              [APPLICATION 36] CVDate,
      certExtensions                  [APPLICATION 5]  CVExt OPTIONAL 
    },
    signature                         [APPLICATION 55] OCTET STRING
  }

  CharString ::= PrintableString(SIZE(8..12))

  PubKey ::= SEQUENCE {
    objIdentifier        OBJECT IDENTIFIER,
    pubKeyandParameters  PublicKey 
  }

  CVDate ::= OCTET STRING(SIZE(6)) -- YYMMDD
  CVExt ::= SEQUENCE OF DiscretionaryDataTemplate
END
